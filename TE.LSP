;-------------------------------------------------------------
; This program is to write TEXT on drawing editor with uniform space
; between lines.
(defun c:te(/ spt txt z) 
     (setvar "cmdecho" 0)  
     (command "osnap" "none")
     (setq oht ht os s
	   spt (getpoint "\n Pick start point of the text : "))
     (princ "\n Height of the text < ") (princ ht)
     (setq  ht (getdist spt " > : "))
     (princ "\n Enter space between lines < ") (princ s)
     (setq   s (getdist spt " > : "))
     (if ht (setq oth ht) (setq ht oth))
     (if s  (setq os s) (setq s os))
     (while (<= s ht)
	    (progn 
			   (prompt "\n * SPACE SHOULD BE MORE THAN TEXT HEIGHT *")
	       (setq s (getdist spt "\n Enter new spacing between lines : "))
	    )
	 )
     (if s (setq os s) (setq s os)) 
     (setq ang (getangle spt "\n Enter orientation angle <0>: ")
	   txt (getstring "\n Enter text to write  : " t)
	     z (getvar "textsize")
     )
     (cond ((= ang nul) (setq ang 0)))
	 (initget "Y N")
	 (setq frg (getkword "\nDo you need DOWN WARD Lines Y/N - <Y> : "))    
     (cond ((= frg nil) (setq rg (* 1.5 pi)))
	   ((= frg "Y") (setq rg (* 1.5 pi)))
	   ((= frg "N") (setq rg (* 0.5 pi)))
     )             
	 (command "style" "" "" 0 "" "" "" "" "")
     (setvar "blipmode" 0)
	 (while (/= txt "")
		    (command "text" spt ht ang txt)
			(setq spt (polar spt (+ ang rg) s)
			      txt (getstring "\n Enter next line : " t))                           
	 )               
     (command "style" "" "" z "" "" "" "" ""
		  "osnap" "int")
	 (setvar "cmdecho" 1) (setvar "blipmode" 1) (princ)
)
