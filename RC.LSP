;THIS PROGRAM DRAWS THE RECTANGLE BY GIVING HEIGHT & WIDTH
;+*+*+*+*+*+*+*+*+*+*+*+*+*+*+*+*+*+*+*+*+*+*+*+*+*+*+*+*+
(defun dr(x)
	(* pi (/ x 180.0)))
(defun rd(x)
    (* 180 (/ x pi)))
(defun C:RC(/ os a c b d)
(setvar "cmdecho" 0) (setvar "blipmode" 1)
(if (or (= ht nil) (= ht 0)) (setq ht 10)) 
(if (or (= w nil) (= w 0)) (setq w 10)) 
(setq os (getvar "osmode" )
      hto ht wo w 
	  a (getpoint "\n Pick corner point of Rectangle : "))
(PRINC "\n Enter Height of Rectangle < ") (princ ht)
(setq ht (getdist  " > : "))
(cond ((= ht nul) (setq ht hto)))
(princ "\n Enter Width of Rectangle < ") (princ w)
(setq w (getdist  " > : "))
(cond ((= w nul) (setq w wo)))
(cond ((= ang nil) (setq ang 0)))
(princ "\n Rotation angle < ") (princ (rtos (rd ang)))
(setq ang (getangle  " > : "))
(cond ((= ang nul) (setq ang ango)))
(cond ((= ang nil) (setq ang 0)))
(while a
  (setq c (polar a ang w)
	    b (polar a (+ ang (dr 90)) ht)
	    d (polar b ang w)
        hto ht wo w ango ang)
  (command "blipmode" "off" "osnap" "none"
	    "pline" a b d c "c")
  (setq  a (getpoint "\n Pick next corner point of Rectangle <exit> : "))
)
(setvar "osmode" os)
(setvar "cmdecho" 1)
(princ "..thanks")
(princ)
)
