(defun dr(x)
    (* pi (/ x 180.0)))
(defun rd(x)
    (* 180.0 (/ x pi)))
(defun c:rail(/ ab ac ad ae af ag ah ai aj ak al am an ao)
	(setvar "cmdecho" 0) (setvar "blipmode" 0)
	(initget 1 "30 40 50 60 70 80 90") 
	(setq ab (getkword "\n  Select Rail Size < 30, 40, 50, 60, 70, 80 or 90 -Lbs > : ")
	      ac (getpoint "\n  Pick base center point : ")
		  ad (getangle ac "\n  Enter rotation angle <0> : ")
	)
    (cond ((= ad nul) (setq ad 0)))
	(cond ((= ab "30") 
 			  (setq ae (polar ac (+ ad 0) 38.1)
					af (polar ae (+ ad (dr 90)) 3.4322)
					ag (polar af (+ ad (dr 130.27)) 3.2319)
					ah (polar ag (+ ad (dr 170.54)) 26.0099)
					ai (polar ah (+ ad (dr 130.25)) 10.2164)
					aj (polar ai (+ ad (dr 90)) 35.4857)
					ak (polar aj (+ ad (dr 54.2)) 2.9226) 
					al (polar ak (+ ad (dr 18.43)) 15.9843)
					am (polar al (+ ad (dr 90)) 10.62)
	                an (polar am (+ ad (dr 135)) 11.1723)
			        ao (polar an (+ ad (dr 180)) 12.75)
			  )
          )
	)		  
	(cond ((= ab "40") 
 			  (setq ae (polar ac (+ ad 0) 44.45)
					af (polar ae (+ ad (dr 90)) 3.5581)
					ag (polar af (+ ad (dr 130.27)) 3.8787)
					ah (polar ag (+ ad (dr 170.55)) 29.8581)
					ai (polar ah (+ ad (dr 130.27)) 12.2824)
					aj (polar ai (+ ad (dr 90)) 41.6534)
					ak (polar aj (+ ad (dr 54.18)) 3.5113) 
					al (polar ak (+ ad (dr 18.36)) 18.1176)
					am (polar al (+ ad (dr 90)) 11.6)
	                an (polar am (+ ad (dr 135)) 13.435)
			        ao (polar an (+ ad (dr 180)) 14.3)
			  )
          )
	)
	(cond ((= ab "50") 
 			  (setq ae (polar ac (+ ad 0) 50)
					af (polar ae (+ ad (dr 90)) 3.8049)
					ag (polar af (+ ad (dr 130.27)) 4.5248)
					ah (polar ag (+ ad (dr 170.54)) 34.6575)
					ai (polar ah (+ ad (dr 130.27)) 12.2816)
					aj (polar ai (+ ad (dr 90)) 48.6944)
					ak (polar aj (+ ad (dr 54.18)) 4.0962) 
					al (polar ak (+ ad (dr 18.37)) 19.8652)
					am (polar al (+ ad (dr 90)) 14.7)
	                an (polar am (+ ad (dr 135)) 13.435)
			        ao (polar an (+ ad (dr 180)) 16.7)
			  )
          )
	)
	(cond ((= ab "60") 
 			  (setq ae (polar ac (+ ad 0) 54.75)
					af (polar ae (+ ad (dr 90)) 4.21)
					ag (polar af (+ ad (dr 130.28)) 5.1724)
					ah (polar ag (+ ad (dr 170.56)) 38.4336)
					ai (polar ah (+ ad (dr 130.28)) 12.2843)
					aj (polar ai (+ ad (dr 90)) 53.7333)
					ak (polar aj (+ ad (dr 54.2)) 4.6794) 
					al (polar ak (+ ad (dr 18.4)) 21.3553)
					am (polar al (+ ad (dr 90)) 16.7)
	                an (polar am (+ ad (dr 135)) 13.435)
			        ao (polar an (+ ad (dr 180)) 19.05)
			  )
          )
	)
    (cond ((= ab "70") 
 			  (setq ae (polar ac (+ ad 0) 58.75)
					af (polar ae (+ ad (dr 90)) 4.6885)
					ag (polar af (+ ad (dr 130.26)) 5.8169)
					ah (polar ag (+ ad (dr 170.53)) 39.9107)
					ai (polar ah (+ ad (dr 130.26)) 14.3484)
					aj (polar ai (+ ad (dr 90)) 57.9151)
					ak (polar aj (+ ad (dr 54.17)) 5.2675) 
					al (polar ak (+ ad (dr 18.35)) 21.8264)
					am (polar al (+ ad (dr 90)) 17)
	                an (polar am (+ ad (dr 135)) 15.6978)
			        ao (polar an (+ ad (dr 180)) 19.05)
			  )
          )
	)
	(cond ((= ab "80") 
 			  (setq ae (polar ac (+ ad 0) 63.5)
					af (polar ae (+ ad (dr 90)) 5.1077)
					ag (polar af (+ ad (dr 130.27)) 5.8175)
					ah (polar ag (+ ad (dr 170.54)) 44.3164)
					ai (polar ah (+ ad (dr 130.27)) 14.35)
					aj (polar ai (+ ad (dr 90)) 63.7266)
					ak (polar aj (+ ad (dr 54.21)) 5.2627) 
					al (polar ak (+ ad (dr 18.43)) 23.1077)
					am (polar al (+ ad (dr 90)) 19.22)
	                an (polar am (+ ad (dr 135)) 15.6978)
			        ao (polar an (+ ad (dr 180)) 20.65)
			  )
          )
	)
	(cond ((= ab "90")
 			  (setq ae (polar ac (+ ad 0) 68.25)
					af (polar ae (+ ad (dr 90)) 4.9941)
					ag (polar af (+ ad (dr 130.27)) 6.4640)
					ah (polar ag (+ ad (dr 170.54)) 47.1496)
					ai (polar ah (+ ad (dr 130.2)) 16.4186)
					aj (polar ai (+ ad (dr 90)) 68.0153)
					ak (polar aj (+ ad (dr 54.97)) 5.7399) 
					al (polar ak (+ ad (dr 18)) 24.2944)
					am (polar al (+ ad (dr 90)) 19.7757)
	                an (polar am (+ ad (dr 135)) 17.9605)
			        ao (polar an (+ ad (dr 180)) 20.65)
			  )
          )
	)
    (command "osnap" "NONE"
             "pline" ac "w" "0" "" ae af "a" ag "l" ah "a" ai 
	         "l" aj "a" ak "l" al am "a" an "l" ao "" 
	         "mirror" "l" "" ac ao ""
		 "pedit" "l" "j" "p" "" ""
		
	) 
	(c:normal) 
	(princ "\n  ") (princ ab) (princ " rail - Drawn.") (princ)
)
