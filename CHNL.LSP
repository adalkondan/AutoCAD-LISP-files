; This DRAWs CHANNEL of any std/unstd. size & at any angle.
;-----------------------------------------------------------
(defun dr(x)
    (* pi (/ x 180.0)))
(defun rd(x)
    (* 180.0 (/ x pi)))
(defun c:ch(/ a b c d e f g h ht w ang tw b1)
       (setvar "cmdecho" 0) (setvar "blipmode" 0)
	   (setq a (getpoint  "\n Pick corner point of HEIGHT : ")
	         ht(getdist a "\n   Enter   HEIGHT of channel : ")
	         w (getdist a "\n   Enter    WIDTH of channel : ")
			ang(getangle a "\n   Enter Rotation angle  <0> : "))
       (cond ((= ang nul) (setq ang 0)))			 
       (setq tw(* 0.075 w)
	         b1(- w tw)
	         b (polar a ang w) 
	         c (polar b (+ ang (dr 90)) tw)
	         d (polar c (+ ang (dr 172)) (/ b1 (cos (dr 6))))
			 h (polar a (+ ang (dr 90)) ht)
			 g (polar h ang w)
			 f (polar g (+ ang (dr 270)) tw)
			 e (polar f (+ ang (dr 186)) (/ b1 (cos (dr 6)))))		 
	   (command "osnap" "none"
	            "pline" a "w" "0" "" b c d e f g h "C" "osnap" "inter")
	   (setvar "cmdecho" 1) (setvar "blipmode" 1) 	   
	   (princ "\n-Channel Drawn-")
	   (prin1)
)
(DEFUN C:CHNL()
	(SETVAR "CMDECHO" 0) (SETVAR "BLIPMODE" 0)
	(INITGET 1 "100 125 150 200 250 300 350 400")
	(SETQ BA (GETKWORD "\n  Select CHANNEL Size -
     ( 100, 125, 150, 200, 250, 300, 350 or 400 ) : ")
		  BB (GETPOINT "\n  Pick Base Corner Point :")
		  BC (GETANGLE "\n  Enter Rotation Angle <0> : "))
    (COND ((= BC nul) (setq BC 0)))
	(COND ((= BA "100")
			(SETQ BD (POLAR BB (+ BC 0) 50)
		    	  BE (POLAR BD (+ BC (DR 90)) 1.0676)
				  BF (POLAR BE (+ BC (DR 132)) 6.0222)
				  BG (POLAR BF (+ BC (DR 174)) 33.3941)
				  BH (POLAR BG (+ BC (DR 132)) 12.0444)
				  BI (POLAR BH (+ BC (DR 90)) 64.0315)
				  BJ (POLAR BI (+ BC (DR 48)) 12.0444)
				  BK (POLAR BJ (+ BC (DR 6)) 33.3941)
				  BL (POLAR BK (+ BC (DR 48)) 6.0222)
				  BM (POLAR BL (+ BC (DR 90)) 1.0676)
				  BN (POLAR BM (+ BC (DR 180)) 50)
			)
		  )
	)
	(COND ((= BA "125")
			(SETQ BD (POLAR BB (+ BC 0) 65)
		    	  BE (POLAR BD (+ BC (DR 90)) 0.4449)
				  BF (POLAR BE (+ BC (DR 132)) 6.6913)
				  BG (POLAR BF (+ BC (DR 174)) 47.2746)
				  BH (POLAR BG (+ BC (DR 132)) 12.7135)
				  BI (POLAR BH (+ BC (DR 90)) 85.3861)
				  BJ (POLAR BI (+ BC (DR 48)) 12.7135)
				  BK (POLAR BJ (+ BC (DR 6)) 47.2746)
				  BL (POLAR BK (+ BC (DR 48)) 6.6913)
				  BM (POLAR BL (+ BC (DR 90)) 0.4449)
				  BN (POLAR BM (+ BC (DR 180)) 65)
			)
		  )
	)
	(COND ((= BA "150")
			(SETQ BD (POLAR BB (+ BC 0) 75)
		    	  BE (POLAR BD (+ BC (DR 90)) 0.8404)
				  BF (POLAR BE (+ BC (DR 132)) 6.6913)
				  BG (POLAR BF (+ BC (DR 174)) 56.4773)
				  BH (POLAR BG (+ BC (DR 132)) 13.3826)
				  BI (POLAR BH (+ BC (DR 90)) 106.6767)
				  BJ (POLAR BI (+ BC (DR 48)) 13.3826)
				  BK (POLAR BJ (+ BC (DR 6)) 56.4773)
				  BL (POLAR BK (+ BC (DR 48)) 6.6913)
				  BM (POLAR BL (+ BC (DR 90)) 0.8404)
				  BN (POLAR BM (+ BC (DR 180)) 75)
			)
		  )
	)
	(COND ((= BA "200")
			(SETQ BD (POLAR BB (+ BC 0) 75)
		    	  BE (POLAR BD (+ BC (DR 90)) 2.8269)
				  BF (POLAR BE (+ BC (DR 132)) 7.3604)
				  BG (POLAR BF (+ BC (DR 174)) 54.4229)
				  BH (POLAR BG (+ BC (DR 132)) 14.7209)
				  BI (POLAR BH (+ BC (DR 90)) 150.1494)
				  BJ (POLAR BI (+ BC (DR 48)) 14.7209)
				  BK (POLAR BJ (+ BC (DR 6)) 54.4229)
				  BL (POLAR BK (+ BC (DR 48)) 7.3604)
				  BM (POLAR BL (+ BC (DR 90)) 2.8269)
				  BN (POLAR BM (+ BC (DR 180)) 75)
			)
		  )
	)
	(COND ((= BA "250")
			(SETQ BD (POLAR BB (+ BC 0) 80)
		    	  BE (POLAR BD (+ BC (DR 90)) 4.8665)
				  BF (POLAR BE (+ BC (DR 132)) 8.0296)
				  BG (POLAR BF (+ BC (DR 174)) 57.0943)
				  BH (POLAR BG (+ BC (DR 132)) 16.0591)
				  BI (POLAR BH (+ BC (DR 90)) 192.5282)
				  BJ (POLAR BI (+ BC (DR 48)) 16.0591)
				  BK (POLAR BJ (+ BC (DR 6)) 57.0943)
				  BL (POLAR BK (+ BC (DR 48)) 8.0296)
				  BM (POLAR BL (+ BC (DR 90)) 4.8665)
				  BN (POLAR BM (+ BC (DR 180)) 80)
			)
		  )
	)
	(COND ((= BA "300")
			(SETQ BD (POLAR BB (+ BC 0) 90)
		    	  BE (POLAR BD (+ BC (DR 90)) 3.4171)
				  BF (POLAR BE (+ BC (DR 132)) 8.6987)
				  BG (POLAR BF (+ BC (DR 174)) 65.2960)
				  BH (POLAR BG (+ BC (DR 132)) 17.3974)
				  BI (POLAR BH (+ BC (DR 90)) 240.7289)
				  BJ (POLAR BI (+ BC (DR 48)) 17.3974)
				  BK (POLAR BJ (+ BC (DR 6)) 65.2960)
				  BL (POLAR BK (+ BC (DR 48)) 8.6987)
				  BM (POLAR BL (+ BC (DR 90)) 3.4171)
				  BN (POLAR BM (+ BC (DR 180)) 90)
			)
		  )
	)
	(COND ((= BA "350")
			(SETQ BD (POLAR BB (+ BC 0) 100)
		    	  BE (POLAR BD (+ BC (DR 90)) 2.3676)
				  BF (POLAR BE (+ BC (DR 132)) 9.3678)
				  BG (POLAR BF (+ BC (DR 174)) 73.4977)
				  BH (POLAR BG (+ BC (DR 132)) 18.7357)
				  BI (POLAR BH (+ BC (DR 90)) 288.1296)
				  BJ (POLAR BI (+ BC (DR 48)) 18.7357)
				  BK (POLAR BJ (+ BC (DR 6)) 73.4977)
				  BL (POLAR BK (+ BC (DR 48)) 9.3678)
				  BM (POLAR BL (+ BC (DR 90)) 2.3676)
				  BN (POLAR BM (+ BC (DR 180)) 100)
			)
		  )
	)
	(COND ((= BA "400")
			(SETQ BD (POLAR BB (+ BC 0) 100)
		    	  BE (POLAR BD (+ BC (DR 90)) 3.7437)
				  BF (POLAR BE (+ BC (DR 132)) 10.0370)
				  BG (POLAR BF (+ BC (DR 174)) 71.6444)
				  BH (POLAR BG (+ BC (DR 132)) 20.0739)
				  BI (POLAR BH (+ BC (DR 90)) 332.7814)
				  BJ (POLAR BI (+ BC (DR 48)) 20.0739)
				  BK (POLAR BJ (+ BC (DR 6)) 71.6444)
				  BL (POLAR BK (+ BC (DR 48)) 10.0370)
				  BM (POLAR BL (+ BC (DR 90)) 3.7437)
				  BN (POLAR BM (+ BC (DR 180)) 100)
			)
		  )
	)
    (command "osnap" "none"
             "pline" BB "W" "0" "" BD BE "A" BF "L" BG "A" BH "L" BI "A" BJ
			         "L" BK "A" BL "L" BM BN BB "" 
	         "osnap" "inter"
	) 
	(c:normal)
	(PRINC "- Drawn.") (PRINC)
)
(PROMPT "\n.chnl & ch...Loaded.")
(princ)
