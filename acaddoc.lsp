;--------------------------------------------------------------      
(defun s::startup() (load"ac_bonus"))
(autoload "setupp.lsp" '("setupp"))
(autoload "setupe.lsp" '("setupe"))
(defun c:atp () (if autopath (c:autopath) 
     (progn (load "autopath") (c:autopath))))
(autoload "app.lsp" '("app"))
(autoload "ang.lsp" '("ang"))
(autoload "extra.lsp" '("extra"))
(autoload "ea.lsp" '("ea"))
(autoload "bpl.lsp" '("bpl"))
(autoload "bph.lsp" '("bph"))
(autoload "bolt.lsp" '("bolt"))
(defun c:CONV () (if CONV (c:CONV) (load "CONV")))
(autoload "cln.lsp" '("cln"))
(autoload "chnl.lsp" '("chnl"))
(autoload "gird.lsp" '("gird"))
(defun c:grt () (load "grt"))
(autoload "layers.lsp" '("layers"))
(autoload "strlay.lsp" '("strlay"))
(defun c:mst () (c:mstretch))
(autoload "Multiply.lsp" '("mu"))
(autoload "MULTIPLY1.LSp" '("mu1"))
(defun c:nc  () (c:ncopy))
(defun c:bt  () (c:btrim))
(defun c:bx  () (c:bextend))
(defun c:lym () (c:laymch))
(defun c:lyc () (c:laycur))
(defun c:lyi () (c:layiso))
(defun c:lyf () (c:layfrz))
(defun c:lyo () (c:layoff))
(defun c:lyl () (c:laylck))
(defun c:lyu () (c:layulk))
(autoload "nut.lsp" '("nut"))
(autoload "numh.lsp" '("numh"))
(autoload "numv.lsp" '("numv"))
(autoload "pn.lsp" '("pn"))
(autoload "pn14.lsp" '("pn14"))
(autoload "revision.lsp" '("revision"))
(autoload "rail.lsp" '("rail"))
(autoload "rc.lsp" '("rc"))
(autoload "shaft.lsp" '("shaft"))
(autoload "tap.lsp" '("tap"))
(autoload "tbt.lsp" '("tbt"))
(autoload "tbt1.lsp" '("tbt1"))
(autoload "te.lsp" '("te"))
(autoload "tot.lsp" '("tot"))
(autoload "total.lsp" '("ttl"))
(autoload "tsl.lsp" '("tsl"))
(autoload "turn.lsp" '("turn"))
(autoload "vctt.lsp" '("vctt"))
(autoload "vscale.lsp" '("vscale"))
(defun c:wt () (load "weight"))
;--------------------------------------------------------------
