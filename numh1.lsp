(DEFUN c:NUMH ()
(SETQ FN (GETINT "n/ ENTER THE FIRST NUMBER :" ))
(SETQ LN (GETINT "n/ ENTER THE LAST NUMBER :"))
(SETQ NS (GETINT "n/ ENTER THE No. STEPS:"))
(SETQ DS (GETDIST "n/ ENTER THE SPACING :"))
(SETQ ST (GETPOINT "n/ PICK THE ST. POINT :"))
(COMMAND "TEXT" ST "" FN)
(REPEAT (- (FIX(/ LN NS)) FN)
(SETQ FN (1+ FN))
(SETQ OFD (STRCAT "@" (RTOS DS)"<0"))
(COMMAND "TEXT" OFD "" FN)
 )
)
