(DEFUN c:NUMH ()
(SETQ FN (GETINT "n/ ENTER THE FIRST NUMBER :" ))
(SETQ LN (GETINT "n/ ENTER THE LAST NUMBER :"))
(SETQ DS (GETDIST "n/ ENTER THE OFFSET DIST :"))
(SETQ ST (GETPOINT "n/ PICK THE ST. POINT :"))
(COMMAND "TEXT" ST "" FN)
(REPEAT (- LN FN)
(SETQ FN (1+ FN))
(SETQ OFD (STRCAT "@" (RTOS DS)"<0"))
(COMMAND "TEXT" OFD "" FN)
 )
)
