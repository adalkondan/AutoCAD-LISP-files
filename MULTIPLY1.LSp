; Multiply numbers in text and put in another text- S.Kadiresh
; Updated on 10th March, 1997

;--------
(defun c:mu1(/ ss en fno sno pno ty)
        (setvar "cmdecho" 1)(textpage)
        (princ "\nPick first number text to multiply:")
        (command "select" "si" pause)(setq ss (ssget "P"))
        (setq en (entget (ssname ss 0)))(setq ty (cdr (assoc 0 en)))
        (if (= ty "TEXT") 
                        (setq fno (cdr (assoc 1 en)))
        )
        (princ "Pick second number text to multiply:")
        (command "select" "si" pause)(setq ss (ssget "P"))
        (setq en (entget (ssname ss 0)))(setq ty (cdr (assoc 0 en)))
        (if (= ty "TEXT") 
                (setq sno (cdr (assoc 1 en)))
        )
        (princ "Pick text to put product:")
        (command "select" "si" pause)(setq ss (ssget "P"))
        (setq en (entget (ssname ss 0)))(setq ty (cdr (assoc 0 en)))
        (setq en (ssname ss 0))
        (if (= ty "TEXT") 
	    (progn
              	(setq pno (rtos (* (atof fno) (atof sno) ) 2 2 ))
                       ; 2 * => DECIMALS ACCURACY,USE 2
		(command "change" en "" "" "" "" "" "" pno)
            )	    
        )
        (setq ss (* (atof fno) (atof sno)))(princ "\n\n\n")
        (princ fno)(princ "x")(princ sno)(princ "=")(princ ss)
        (princ "\n\n")(setvar "cmdecho" 1)(princ)
)
;--
(defun c:mu(/ ss en fno sno pno ty)
        (setvar "cmdecho" 1)(textpage)
        (princ "\nPick first number text to multiply:")
        (command "select" "si" pause)(setq ss (ssget "P"))
        (setq en (entget (ssname ss 0)))(setq ty (cdr (assoc 0 en)))
        (if (= ty "TEXT") 
                        (setq fno (cdr (assoc 1 en)))
        )
        (princ "Pick second number text to multiply:")
        (command "select" "si" pause)(setq ss (ssget "P"))
        (setq en (entget (ssname ss 0)))(setq ty (cdr (assoc 0 en)))
        (if (= ty "TEXT") 
                (setq sno (cdr (assoc 1 en)))
        )
        (princ "Pick text to put product:")
        (command "select" "si" pause)(setq ss (ssget "P"))
        (setq en (entget (ssname ss 0)))(setq ty (cdr (assoc 0 en)))
        (setq en (ssname ss 0))
        (if (= ty "TEXT") 
	    (progn
              	(setq pno (rtos (* (atof fno) (atof sno) ) 2 2 ))
                       ; 2 * => DECIMALS ACCURACY,USE 2
		(command "change" en "" "" "" "" "" pno)
            )	    
        )
        (setq ss (* (atof fno) (atof sno)))(princ "\n\n\n")
        (princ fno)(princ "x")(princ sno)(princ "=")(princ ss)
        (princ "\n\n")(setvar "cmdecho" 1)(princ)
)
