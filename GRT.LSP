;to display drg.  name, sheet, scale, date etc, 
;on screen menu  -basu.
;----------------------
 (defun seterr (s)
  (if (/= s "Function cancelled")
      (princ (strcat "\n:ERROR: " s)))
  (setq *error* olderr)
  (princ))
;-----------------
(apply '(lambda (/ ma mal dp sl ts ss ts1 sl1)
 (setvar "cmdecho" 0) 
 (setq olderr *error*
       *error* seterr
       sl (getvar "userr1")
       ts (getvar "textsize")
       ss (getvar "useri1")
       tsy (getvar "textstyle")
      dsy (getvar "dimstyle")
      dms (getvar "dimscale")
      fir (getvar "filletrad")
      ori (getvar "ucsname"))
 (cond ((= ss 0) (setq ss1 "A0"))
       ((= ss 1) (setq ss1 "A1"))
       ((= ss 2) (setq ss1 "A2"))
       ((= ss 3) (setq ss1 "A3"))
       ((= ss 4) (setq ss1 "A4"))
       ((> ss 4) (setq ss1 "non std."))
 )
 (setvar "cmdecho" 1) 
 (setq *error* olderr)
 (PRINC "\n  Present settings of this Drawing--") 
 (princ "\n UCS:") (princ ori )
 (princ "   Fillet r:") (princ fir )
 (princ "   Dimstyle:") (princ dsy )
 (princ "   Dimscale:") (princ dms)
 (princ "\n Textstyle:") (princ tsy )
 (princ "   Text Ht:") (princ ts ) 
 (princ "   Format:") (princ ss1 )
 (princ "   DRG Scale:") (princ sl ) (princ)
 ) '()
)
