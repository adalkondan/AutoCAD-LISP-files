;to forget convertion formulas & work till yoy get bored.  -basu.
;---------------------------------------------------------------
(princ "\n...Convertion FORMULAs. .. ...")
(defun c:conv()
(textscr)
(princ "\n.Loaded Convertion FORMULAs. .. ...")
(princ "\nd-r, r-d,   i-mm, mm-i,   f-m, m-f,   kg-lb, lb-kg,   y-m, m-y,   mi-km, km-mi,")
(princ "\nsqi-sqcm, sqi-sqmm, sqcm-sqi, sqmm-sqi, sqf-sqm, sqm-sqf, sqmi-sqkm, sqkm-sqmi,")
(princ "\ncum-cuf, cuf-cum,      cui-cucm, cucm-cui,      kg/scm-lb/si,     lb/si-kg/scm,")
(princ "\ncuf-l, l-cuf, g-l, l-g.                   (.call as listed here.)")
(princ)
)
(defun c:d-r(/ x y)
    (while (/= (setq x(getreal "\ndegree-  ")) nul)
	(setq y(* pi (/ x 180.0))) (princ " = ") (princ y) (princ)))
(defun c:r-d(/ x y)
    (while (/= (setq x(getreal "\nradians-  ")) nul)
	(setq y(* 180.0 (/ x pi))) (princ " = ") (princ y) (princ)))
(defun c:i-mm(/ x y)
  (while (/= (setq x(getreal "\nInch-  ")) nul)
    (setq y(* 25.4 x)) (princ " = ") (princ y) (princ)))
(defun c:mm-i(/ x y)
  (while (/= (setq x(getreal "\nmm-  ")) nul)
    (setq y(/ x 25.4)) (princ " = ") (princ y) (princ)))    
(defun c:f-m(/ x y)
  (while (/= (setq x(getreal "\nFeet-  ")) nul)
    (setq y(* 0.3048 x)) (princ (strcat " = " (rtos y) " mtr.")) (princ)))    
(defun c:m-f(/ x y)
  (while (/= (setq x(getreal "\nMeter-  ")) nul)
    (setq y(/ x 0.3048)) (princ (Strcat " = " (rtos y) " feet.")) (princ)))    
(defun c:kg-lb(/ x y)
  (while (/= (setq x(getreal "\n Kgs. -  ")) nul)
    (setq y (* x 2.2046223)) (princ (strcat " = " (rtos y) " lbs.")) (princ)))
(defun c:lb-kg(/ x y)
  (while (/= (setq x(getreal "\n Lbs. -  ")) nul)
    (setq y (/ x 2.2046223)) (princ (strcat " = " (rtos y) " kgs.")) (princ)))
(defun c:y-m(/ x y)
  (while (/= (setq x(getreal "\n Yards -  ")) nul)
    (setq y (* x 0.9144)) (princ (strcat " = "  (rtos y) " Mtrs.")) (princ)))
(defun c:m-y(/ x y)
  (while (/= (setq x(getreal "\n Meter -  ")) nul)
    (setq y (* x 1.0936)) (princ (strcat " = " (rtos y) " yards.")) (princ)))
(defun c:mi-km(/ x y)
  (while (/= (setq x(getreal "\n Mile - ")) nul)
    (setq y (* x 1.609347)) (princ (strcat " = " (rtos y) " km.")) (princ)))
(defun c:km-mi(/ x y)
  (while (/= (setq x(getreal "\n Kilometer - ")) nul)
    (setq y (* x 0.621370)) (princ (strcat " = " (rtos y) " mile.")) (princ)))	
;------
(defun c:sqi-sqcm(/ x y)
  (while (/= (setq x(getreal "\n sq.inch - ")) nul)
    (setq y (* x 6.45163)) (princ (strcat " = " (rtos y) " sq.cm.")) (princ)))
(defun c:sqi-sqmm(/ x y)
  (while (/= (setq x(getreal "\n sq.inch - ")) nul)
    (setq y (* x 645.163)) (princ (strcat " = " (rtos y) " sq.mm.")) (princ)))
(defun c:sqcm-sqi(/ x y)
  (while (/= (setq x(getreal "\n sq.cm - ")) nul)
    (setq y (* x 0.155)) (princ (strcat " = " (rtos y) " sq.in.")) (princ)))
(defun c:sqmm-sqi(/ x y)
  (while (/= (setq x(getreal "\n sq.mm - ")) nul)
    (setq y (* x 0.00155)) (princ (strcat " = " (rtos y) " sq.in.")) (princ)))
(defun c:sqf-sqm(/ x y)
  (while (/= (setq x(getreal "\n sq.feet - ")) nul)
    (setq y (* x 0.0929034)) (princ (strcat " = " (rtos y) " sq.mtr.")) (princ)))		
(defun c:sqm-sqf(/ x y)
  (while (/= (setq x(getreal "\n sq.mtr. - ")) nul)
    (setq y (* x 10.76387)) (princ (strcat " = " (rtos y) " sq.feet.")) (princ)))	
(defun c:sqmi-sqkm(/ x y)
  (while (/= (setq x(getreal "\n sq.mile - ")) nul)
    (setq y (* x 2.5899)) (princ (strcat " = " (rtos y) " sq.km.")) (princ)))		
(defun c:sqkm-sqmi(/ x y)
  (while (/= (setq x(getreal "\n sq.km. - ")) nul)
    (setq y (* x 0.3861)) (princ (strcat " = " (rtos y) " sq.mile.")) (princ)))	
;------
(defun c:cui-cucm(/ x y)
  (while (/= (setq x(getreal "\n cu.inch - ")) nul)
    (setq y (* x 16.38716)) (princ (strcat " = " (rtos y) " cu.cm.")) (princ)))	
(defun c:cucm-cui(/ x y)
  (while (/= (setq x(getreal "\n cu.cm - ")) nul)
    (setq y (* x 0.061)) (princ (strcat " = " (rtos y) " cu.inch.")) (princ)))	
(defun c:cuf-cum(/ x y)
  (while (/= (setq x(getreal "\n cu.feet - ")) nul)
    (setq y (* x 0.028317)) (princ (strcat " = " (rtos y) " cu.mtr.")) (princ)))	
(defun c:cum-cuf(/ x y)
  (while (/= (setq x(getreal "\n cu.mtr - ")) nul)
    (setq y (* x 35.31445)) (princ (strcat " = " (rtos y) " cu.feet.")) (princ)))
(defun c:cuf-l(/ x y)
  (while (/= (setq x(getreal "\n cu.feet - ")) nul)
    (setq y (* x 28.31622)) (princ (strcat " = " (rtos y) " Liters.")) (princ)))	
(defun c:l-cuf(/ x y)
  (while (/= (setq x(getreal "\n Liters - ")) nul)
    (setq y (* x 0.0353154)) (princ (strcat " = " (rtos y) " cu.feet.")) (princ)))
(defun c:g-l(/ x y)
  (while (/= (setq x(getreal "\n Gallons - ")) nul)
    (setq y (* x 3.785329)) (princ (strcat " = " (rtos y) " Liters.")) (princ)))	
(defun c:l-g(/ x y)
  (while (/= (setq x(getreal "\n Liters - ")) nul)
    (setq y (* x 0.264178)) (princ (strcat " = " (rtos y) " Gallons.")) (princ)))
;------
(defun c:kg/scm-lb/si(/ x y)
  (while (/= (setq x(getreal "\n kg/sq.cm. - ")) nul)
    (setq y (* x 14.2234)) (princ (strcat " = " (rtos y) " lb/sq.inch.")) (princ)))
(defun c:lb/si-kg/scm(/ x y)
  (while (/= (setq x(getreal "\n lb/sq.inch. - ")) nul)
    (setq y (* x 0.0703066)) (princ (strcat " = " (rtos y) " kg/sq.cm.")) (princ)))
;------------------------------------------------------------------------------------------------
(textscr)
(princ "\nd-r, r-d,   i-mm, mm-i,   f-m, m-f,   kg-lb, lb-kg,   y-m, m-y,   mi-km, km-mi,")
(princ "\nsqi-sqcm, sqi-sqmm, sqcm-sqi, sqmm-sqi, sqf-sqm, sqm-sqf, sqmi-sqkm, sqkm-sqmi,")
(princ "\ncum-cuf, cuf-cum,      cui-cucm, cucm-cui,      kg/scm-lb/si,     lb/si-kg/scm,")
(princ "\ncuf-l, l-cuf, g-l, l-g.                   (.call as listed here.)")
(princ "\n ... . ... . ... ... ... Loaded.")
(princ)
