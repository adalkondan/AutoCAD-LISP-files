(defun c:tbt()
  (setq e (nentsel "Select the text: ")
        en(car e)
        enb(car (last e))
        el (entget en)
        hl(assoc 40 el)
        h (cdr hl)
        nh(* 0.7 h)
        nhl (cons 40 nh)
        el (subst nhl hl el)
   )
   (entmod el)
    (entupd enb)
)
