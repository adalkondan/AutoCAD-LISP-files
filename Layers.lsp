;This spl layer setup prg is created for wil -  basavaraju June-99.
;-----------------------------------------------------------
(DEFUN LAYT (lanam clrno lintyp)
   (setq ts (tblsearch "LAYER" LANAM))
   (if (null ts) 
      (PROGN 
        (prompt "..Creating new layer..") 
        (PRINC LANAM) 
        (PRINC "\n")
        (COMMAND "LAYER" "M" LANAM "C" CLRNO LANAM "lt" lintyp lanam "" )
      )
   )
)
;--------------------------
(DEFUN C:LAYERS()
(setvar "cmdecho" 0)
(LAYT "cl" 252 "center")
(LAYT "fl" 31 "continuous")
(LAYT "fm" 201 "continuous")
(LAYT "hl" 92 "hidden")
(LAYT "hm" 220 "hidden")
(LAYT "pl" 32 "phantom")
(LAYT "sh" 10 "continuous")
(LAYT "sl" 211 "continuous")
(LAYT "sm" 110 "continuous")
(LAYT "sx" 50 "continuous")
(LAYT "xa" 70 "continuous")
(LAYT "xb" 252 "center")
(LAYT "xd" 150 "continuous")
(LAYT "xe" 210 "continuous")
(LAYT "xf" 106 "continuous")
(LAYT "xp" 232 "phantom")
(LAYT "xt" 130 "continuous")
(LAYT "xu" 120 "continuous")
(LAYT "xv" 31 "continuous")
 (setvar "clayer" "0")
 (setvar "cmdecho" 1)
 (princ "\n--Layers ready.")
 (princ)
)
