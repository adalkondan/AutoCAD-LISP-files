;THIS PROGRAM DRAWS THE shaft BY GIVING length & Dia By Murali
;+*+*+*+*+*+*+*+*+*+*+*+*+*+*+*+*+*+*+*+*+*+*+*+*+*+*+*+*+*+*+
(Defun dr(x)
	(* pi (/ x 180.0)))
(defun rd(x)
    (* 180 (/ x pi)))
(defun C:SHAFT(/ os xx aa bb cc dd )
 (setvar "cmdecho" 0) (setvar "blipmode" 0)
 (setq os (getvar "osmode" )
      try "y" ang 0
      xx (getpoint "\n Pick Start point of Shaft: "))
 (setq ang (getangle "\n Enter Rotation angle <0> : "))
 (if (= ang nul) (setq ang 0))	  
 (while (or (= try "Y") (= try "y"))  
        (setq lt lto d do )
        (PRINC "\n Enter Length of Shaft < ") (princ lt)
        (setq lt (getdist " > : "))
        (cond ((= lt nul) (setq lt lto)))
        (princ "\n Enter Dia of Shaft < ") (princ d)
        (setq d (getdist " > : "))
        (cond ((= d nul) (setq d do)))
        (setq aa (polar xx (+ ang (dr 270)) (/ d 2))
	          bb (polar aa ang lt)
	          cc (polar bb (+ ang (dr 90)) d)
		      dd (polar cc (+ ang (dr 180)) lt)
	            lto lt do d)
	    (command "osnap" "none"
	             "pline" aa bb cc dd  "c")
	    (setq try (getstring "\n DO U WISH for Next Step y/n <Y>...."))
	    (if (or (= try "") (= try "y") (= try "Y"))
	        (setq try "Y" xx (polar xx ang lt)))
 )
 (setvar "osmode" os)
 (setvar "cmdecho" 1) (setvar "blipmode" 1)
 (princ "..thanks")
 (princ)
)
