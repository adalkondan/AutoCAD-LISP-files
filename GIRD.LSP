;TO LIST & LOAD GIRDER MACRO
;-------------------------------
(defun c:gird()
	(textscr)
	(prompt "            THE AVAILABLE MEDIUM BEAM SECTIONS ARE : - ") 
	(print) (print)
	(prompt "        600  ,  550  ,  500  ,  450  ,  400  ,  350  ,  300  ")
	(print)
	(prompt "        250  ,  225  ,  200  ,  175  ,  150  ,  125  , 100  ")
	(print)(print)
	(prompt "  To draw a section use SECTION NUMBER followed by I (Ex. 600I)")
	(print)(print)
    (prompt "  To draw UNSTANARD SECTION type GIRDER") 	
	(print)
)	
(DEFUN C:600I() (LOAD "600I") (C:600I))
(DEFUN C:550I() (LOAD "550I") (C:550I))
(DEFUN C:500I() (LOAD "500I") (C:500I))
(DEFUN C:450I() (LOAD "450I") (C:450I))
(DEFUN C:400I() (LOAD "400I") (C:400I))
(DEFUN C:350I() (LOAD "350I") (C:350I))
(DEFUN C:300I() (LOAD "300I") (C:300I))
(DEFUN C:250I() (LOAD "250I") (C:250I))
(DEFUN C:225I() (LOAD "225I") (C:225I))
(DEFUN C:200I() (LOAD "200I") (C:200I))
(DEFUN C:175I() (LOAD "175I") (C:175I))
(DEFUN C:150I() (LOAD "150I") (C:150I))
(DEFUN C:125I() (LOAD "125I") (C:125I))
(DEFUN C:100I() (LOAD "100I") (C:100I))
