; to change old text  to new/present style.   - jan-1993 -Basu.
;-----------------------------------------------------------------
(defun myerror (s)
   (if (/= s "Function cancelled")  
      (princ (strcat "\nError: " s))
   )
   (setq p nil)                     
   (setq *error* olderr)            
   (princ)
)
(DEFUN C:TSY ()
   (setvar "cmdecho" 0) 
   (setq olderr  *error*
         *error* myerror
         chm     0)
   (setq  ts (getvar "textstyle"))
   (setq p (ssget))
   (if p 
     (progn (setq l 0 n(sslength p))
            (princ "\n(For all text lines) New style / <present setting - ") 
			(princ ts)
            (setq nts(getstring "> : "))
            (cond ((= nts "") (setq nts ts)))    
		(while (< l n)
            (setq en(cdr (assoc 0 (setq pl(entget (ssname p l))))))
			(cond ((= en "TEXT") 
                   (progn
				     (setq a  (assoc 7 pl)
					       b  (cons 7 nts)
		                   c  (subst b a pl)
					 ) 
					 (entmod c)   
					 (setq chm (1+ chm))
		           )
	              )
		    ) (setq l (1+ l))
	    )
	 )
   )
   (princ "Changed ")
   (princ chm)
   (princ " text lines.")
   (terpri)
   (setq *error* olderr)
   (setvar "cmdecho" 1)
   (princ)
)
