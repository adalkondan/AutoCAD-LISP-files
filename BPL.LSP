;THIS PROGRAM DRAWS BASE PLATE HOLES BY GIVING SPACING
;+*+*+*+*+*+*+*+*+*+*+*+*+*+*+*+*+*+*+*+*+*+*+*+*+*+*+
(defun dr(x)
	(* pi (/ x 180.0)))
(defun rd(x)
    (* 180 (/ x pi)))
(defun C:BPL(/ SP SPB os a c b d)
(setvar "cmdecho" 0)
(setvar "blipmode" 1)
 (setvar "pdmode" 2)
(setq ht hto w wo 
      SP (getpoint "\n Pick CENTRE point of Rectangle : "))
(PRINC "\n Enter Height of Rectangle < ") (princ ht)
(setq ht (getdist  " > : "))
(cond ((= ht nul) (setq ht hto)))
(princ "\n Enter Width of Rectangle < ") (princ w)
(setq w (getdist  " > : "))
(cond ((= w nul) (setq w wo)))
(cond ((= ang nil) (setq ang 0)))
(princ "\n Rotation angle < ") (princ (rtos (rd ang)))
(setq ang (getangle  " > : "))
(cond ((= ang nul) (setq ang ango)))
(cond ((= ang nil) (setq ang 0)))
(while SP
  (setq   spb (polar sp (+ ang (dr 270)) (/ ht 2))
   	    a (polar spb (+ ang pi) (/ w 2))
            b (polar a ang w)
	    c (polar b (+ ang (dr 90)) ht)
	    d (polar a (+ ang (dr 90)) ht)
	    hto ht wo w ango ang)
   (COMMAND "osnap" "none" "POINT" SP "PLINE" a b c d "c" )
   (setq  SP (getpoint "\n Pick next CENTER point of Rectangle <exit> : "))
)
(c:normal)
(princ "..thanks")
(princ)
)
