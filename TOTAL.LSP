; Total of lines selected
(defun c:ttl(/ ss tot i len en fpt lpt nlen ty)
        (setvar "cmdecho" 0)(textpage)
        (setq ss (ssget))
        (setq tot (sslength ss))
        (setq i 0)(setq len 0)
        (while (< i tot)
                (setq en (entget (ssname ss i)))
                (setq ty (cdr (assoc 0 en)))
                (if (= ty "LINE") (progn
                        (setq fpt (cdr (assoc 10 en)))
                        (setq lpt (cdr (assoc 11 en)))
                        (setq nlen (distance fpt lpt))
                        (print nlen)
                        (setq len (+ len nlen))
                ))
                (setq i (+ 1 i))
                
        )
        (textscr)
        (princ "\n\n")
       (princ "Total length =")(princ len)
        (setvar "cmdecho" 1)
)
