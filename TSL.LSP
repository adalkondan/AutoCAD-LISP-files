; to change old text ht. to new/present ht.   - jan-1993 -Basu.
;--------------------------------------------------------------
(defun myerror (s)
   (if (/= s "Function cancelled")  
      (princ (strcat "\nError: " s))
   )
   (setq p nil)                     
   (setvar "cmdecho" 0) 
   (setq *error* olderr)            
   (princ)
)
(DEFUN C:TSL (/ p chm l en pl nth a oth b c)
 (setq olderr  *error*
         *error* myerror
         chm     0)
   (setq  ts (getvar "textsize"))
   (setq p (ssget))
   (if p 
     (progn 
       (setq l 0 n(sslength p))
       (princ "\n(For all text lines) New height / <present setting - ") (princ ts)
       (setq nth(getreal "> : "))
       (cond ((= nth nul) (setq nth ts)))    
       (while (< l n)
            (setq en(cdr (assoc 0 (setq pl(entget (ssname p l))))))
	    (cond ((= en "TEXT") 
                   (progn
		    (setq a  (assoc 40 pl)
                          b  (cons 40 nth)
		          c  (subst b a pl)
		    ) 
		    (entmod c)   (setq chm (1+ chm))
		   )
	          )
	    ) (setq l (1+ l))
	)
     )
   )
   (princ "Changed ")
   (princ chm)
   (princ " text lines.")
   (terpri)
   (setq *error* olderr)
   (setvar "cmdecho" 1)
   (princ)
)
